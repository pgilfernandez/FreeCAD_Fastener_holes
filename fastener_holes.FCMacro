#!/usr/bin/env python
# -*- coding: utf-8 -*-

# ====================================================================================
# ====================================================================================
# ==                                                                                ==
# ==                              Fastener holes                                    ==
# ==                                                                                ==
# ====================================================================================
# ====================================================================================
# ABOUT
# ====================================================================================
# Macro developed for FreeCAD (https://www.freecadweb.org/).
# This macro creates shapes to act as holes when cut to other shapes.
# It makes easy and fast the creation and tweaking of all needed parts.
# It may be very useful when designing parts for 3D printing and others.
#
# LICENSE
# ====================================================================================
# Copyright (c) 2020 Pablo Gil Fernandez
#
# This work is licensed under GNU Lesser General Public License (LGPL).
# To view a copy of this license, visit https://www.gnu.org/licenses/lgpl-3.0.html
#
# ====================================================================================
__title__   = "Fastener holes"
__author__  = "Pablo Gil Fernández"
__version__ = "11.00"
__date__    = "20/02/2020"

__Comment__ = "This macro creates shapes to act as holes when cut to other shapes. It makes easy and fast the creation and tweaking of all needed parts. It may be very useful when designing parts for 3D printing and others."

__Wiki__ = "http://www.freecadweb.org/wiki/index.php?title=Fastener_holes"
__Help__ = ""
__Status__ = "stable"
__Requires__ = "freecad 0.17"

import FreeCAD, FreeCADGui, Draft, Part, PartGui, math, PartDesignGui
from FreeCAD import Base
from PySide import QtGui, QtCore
from math import cos, radians
from pivy import coin
import sys
App = FreeCAD
Gui = FreeCADGui

##--------------------------------------------------------------------------------------
def a_clear_console():
    #clearing previous messages
    mw=FreeCADGui.getMainWindow()
    # c=mw.findChild(QtGui.QPlainTextEdit, "Python console")
    # c.clear()
    r=mw.findChild(QtGui.QTextEdit, "Report view")
    r.clear()
#if not Mod_ENABLED:
a_clear_console()

sizeX = 360
sizeY = 370

def close_dock():
    #def closeEvent(self, e):
    ALGDockWidget.close()
    #self.setWindowState(QtCore.Qt.WindowActive)
    doc=FreeCAD.ActiveDocument
    if doc is not None:
        FreeCAD.setActiveDocument(doc.Name)
    #FreeCAD.ActiveDocument=FreeCAD.getDocument(doc.Label)
    #FreeCADGui.ActiveDocument=FreeCADGui.getDocument(doc.Label)

def Alg_undock():
    ALGDockWidget.setFloating(True)  #undock
    ALGDockWidget.resize(sizeX,sizeY)
    ALGDockWidget.activateWindow()
    ALGDockWidget.raise_()
    #AlgWidget.resize(QtCore.QSize(300,100).expandedTo(AlgWidget.maximumSize())) # sets size of the widget
    #AlgWidget.setFloating(False)  #dock
    #say ("now!")

def Alg_minimz():
    #clear_console()
    ALGDockWidget.setFloating(True)  #undock
    # AlgWidget.hide();
    # AlgWidget.setWindowState(QtCore.Qt.WindowMinimized)
    #AlgWidget.resize(500, 500)
    ALGDockWidget.resize(sizeX,sizeY)
    ALGDockWidget.activateWindow()
    ALGDockWidget.raise_()

def pointAt(normal, up):
    z = normal
    y = up
    x = y.cross(z)
    y = z.cross(x)

    rot = App.Matrix()
    rot.A11 = x.x
    rot.A21 = x.y
    rot.A31 = x.z

    rot.A12 = y.x
    rot.A22 = y.y
    rot.A32 = y.z

    rot.A13 = z.x
    rot.A23 = z.y
    rot.A33 = z.z

    return App.Placement(rot).Rotation


# ##############################################################
# global initial_placement, last_selection
# global moving, rotating
# global objs_moved, plc_moved
#
# #init
# initial_placement = FreeCAD.Placement(App.Vector(0,0,0), App.Rotation(0,0,0), App.Vector(0,0,0)) #Placement [Pos=(0,0,0), Yaw-Pitch-Roll=(0,0,0)]
# moving = [] #[App.Vector(0,0,0)]
# rotating = [] #[0, App.Vector(0,0,0), App.Vector(0,0,0)]
# objs_moved = []
# plc_moved = []
# #Draft.rotate(objs[j],-rot_angle,rot_center,rot_axis)
# #rotating=[rot_angle,rot_center,rot_axis]
#
# last_selection = []
#
# #################################################################

def say(msg):
    FreeCAD.Console.PrintMessage(msg)
    FreeCAD.Console.PrintMessage('\n')

def sayw(msg):
    FreeCAD.Console.PrintWarning(msg)
    FreeCAD.Console.PrintWarning('\n')

def sayerr(msg):
    FreeCAD.Console.PrintError(msg)
    FreeCAD.Console.PrintWarning('\n')

def make_string(input):
    if (sys.version_info > (3, 0)):  #py3
        if isinstance(input, str):
            return input
        else:
            input =  input.encode('utf-8')
            return input
    else:                            #py2
        if type(input) == unicode:
            input =  input.encode('utf-8')
            return input
        else:
            return input

#sayw("Fastener holes v" + str(__version__))

###############################################################################################################
class Ui_DockWidget(object):
    def setupUi(self, DockWidget):
        infoIcon = ['16 16 3 1',
                '   c None',
                '+  c #444444',
                '.  c #e6e6e6',
                '     ......    ',
                '   ..........  ',
                '  ......++.... ',
                ' .......++.....',
                ' ..............',
                '.....+++++......',
                '....+++++.......',
                '.......++.......',
                '.......++.......',
                '.......+........',
                '......++........',
                ' .....++.+.....',
                ' .....++++.....',
                '  .....++..... ',
                '   ..........  ',
                '     ......    ']

        # Hide/show "to column" label and spinbox based on mode type
        def disableWidget(currentIndex):



            if self.d2.currentText() == "Hole":
                iN4.hide()
                self.d4.setEnabled(False)
                iN5.hide()
                self.d5.setEnabled(False)
                iN10.show()
                self.d10.setEnabled(True)
                if self.d10.isChecked():
                    # iN11.show()
                    self.d11.setEnabled(True)
                else:
                    # iN11.hide()
                    self.d11.setEnabled(False)
            elif self.d2.currentText() == "Bolt":
                iN3.show()
                self.d3.setEnabled(True)
                iN4.hide()
                self.d4.setEnabled(False)
                iN5.hide()
                self.d5.setEnabled(False)
                iN10.show()
                self.d10.setEnabled(True)
                if self.d10.isChecked():
                    # iN11.show()
                    self.d11.setEnabled(True)
                else:
                    # iN11.hide()
                    self.d11.setEnabled(False)
            elif self.d2.currentText() == "Bolt and nut":
                iN3.show()
                self.d3.setEnabled(True)
                iN4.hide()
                self.d4.setEnabled(False)
                iN5.show()
                self.d5.setEnabled(True)
                iN10.show()
                self.d10.setEnabled(True)
                if self.d10.isChecked():
                    # iN11.show()
                    self.d11.setEnabled(True)
                else:
                    # iN11.hide()
                    self.d11.setEnabled(False)
            elif self.d2.currentText() == "Bolt and grooved nut":
                iN3.show()
                self.d3.setEnabled(True)
                iN4.show()
                self.d4.setEnabled(True)
                iN5.show()
                self.d5.setEnabled(True)
                iN10.hide()
                self.d10.setChecked(False)
                self.d10.setEnabled(False)
                # iN11.hide()
                self.d11.setEnabled(False)
            elif self.d2.currentText() == "Bolt and washer":
                iN3.show()
                self.d3.setEnabled(True)
                iN4.hide()
                self.d4.setEnabled(False)
                iN5.hide()
                self.d5.setEnabled(False)
                iN10.show()
                self.d10.setEnabled(True)
                if self.d10.isChecked():
                    # iN11.show()
                    self.d11.setEnabled(True)
                else:
                    # iN11.hide()
                    self.d11.setEnabled(False)
            elif self.d2.currentText() == "Bolt and large washer":
                iN3.show()
                self.d3.setEnabled(True)
                iN4.hide()
                self.d4.setEnabled(False)
                iN5.hide()
                self.d5.setEnabled(False)
                iN10.show()
                self.d10.setEnabled(True)
                if self.d10.isChecked():
                    # iN11.show()
                    self.d11.setEnabled(True)
                else:
                    # iN11.hide()
                    self.d11.setEnabled(False)
            elif self.d2.currentText() == "Bolt, nut and washer":
                iN3.show()
                self.d3.setEnabled(True)
                iN4.hide()
                self.d4.setEnabled(False)
                iN5.show()
                self.d5.setEnabled(True)
                iN10.show()
                self.d10.setEnabled(True)
                if self.d10.isChecked():
                    # iN11.show()
                    self.d11.setEnabled(True)
                else:
                    # iN11.hide()
                    self.d11.setEnabled(False)
            elif self.d2.currentText() == "Bolt, nut and large washer":
                iN3.show()
                self.d3.setEnabled(True)
                iN4.hide()
                self.d4.setEnabled(False)
                iN5.show()
                self.d5.setEnabled(True)
                iN10.show()
                self.d10.setEnabled(True)
                if self.d10.isChecked():
                    # iN11.show()
                    self.d11.setEnabled(True)
                else:
                    # iN11.hide()
                    self.d11.setEnabled(False)
            elif self.d2.currentText() == "Bolt, grooved nut and washer":
                iN3.show()
                self.d3.setEnabled(True)
                iN4.show()
                self.d4.setEnabled(True)
                iN5.show()
                self.d5.setEnabled(True)
                iN10.hide()
                self.d10.setChecked(False)
                self.d10.setEnabled(False)
                # iN11.hide()
                self.d11.setEnabled(False)
            elif self.d2.currentText() == "Bolt, grooved nut and large washer":
                iN3.show()
                self.d3.setEnabled(True)
                iN4.show()
                self.d4.setEnabled(True)
                iN5.show()
                self.d5.setEnabled(True)
                iN10.hide()
                self.d10.setChecked(False)
                self.d10.setEnabled(False)
                # iN11.hide()
                self.d11.setEnabled(False)
            elif self.d2.currentText() == "Nut":
                iN3.hide()
                self.d3.setEnabled(False)
                iN4.hide()
                self.d4.setEnabled(False)
                iN5.hide()
                self.d5.setEnabled(False)
                iN10.show()
                self.d10.setEnabled(True)
                if self.d10.isChecked():
                    # iN11.show()
                    self.d11.setEnabled(True)
                else:
                    # iN11.hide()
                    self.d11.setEnabled(False)
            elif self.d2.currentText() == "Grooved nut":
                iN3.hide()
                self.d3.setEnabled(False)
                iN4.show()
                self.d4.setEnabled(True)
                iN5.hide()
                self.d5.setEnabled(False)
                iN10.hide()
                self.d10.setChecked(False)
                self.d10.setEnabled(False)
                # iN11.hide()
                self.d11.setEnabled(False)
            elif self.d2.currentText() == "Nut and washer":
                iN3.hide()
                self.d3.setEnabled(False)
                iN4.hide()
                self.d4.setEnabled(False)
                iN5.hide()
                self.d5.setEnabled(False)
                iN10.show()
                self.d10.setEnabled(True)
                if self.d10.isChecked():
                    # iN11.show()
                    self.d11.setEnabled(True)
                else:
                    # iN11.hide()
                    self.d11.setEnabled(False)
            elif self.d2.currentText() == "Nut and large washer":
                iN3.hide()
                self.d3.setEnabled(False)
                iN4.hide()
                self.d4.setEnabled(False)
                iN5.hide()
                self.d5.setEnabled(False)
            elif self.d2.currentText() == "Grooved nut and washer":
                iN3.hide()
                self.d3.setEnabled(False)
                iN4.show()
                self.d4.setEnabled(True)
                iN5.hide()
                self.d5.setEnabled(False)
                iN10.hide()
                self.d10.setChecked(False)
                self.d10.setEnabled(False)
                # iN11.hide()
                self.d11.setEnabled(False)
            elif self.d2.currentText() == "Grooved nut and large washer":
                iN3.hide()
                self.d3.setEnabled(False)
                iN4.show()
                self.d4.setEnabled(True)
                iN5.hide()
                self.d5.setEnabled(False)
                iN10.hide()
                self.d10.setChecked(False)
                self.d10.setEnabled(False)
                # iN11.hide()
                self.d11.setEnabled(False)
            else:
                iN3.hide()
                self.d3.setEnabled(False)
                iN4.hide()
                self.d4.setEnabled(False)
                iN5.hide()
                self.d5.setEnabled(False)
                iN10.hide()
                self.d10.setChecked(False)
                self.d10.setEnabled(False)
                # iN11.hide()
                self.d11.setEnabled(False)

        DockWidget.setObjectName("DockWidget")
        DockWidget.resize(sizeX, sizeY)
        DockWidget.setLayoutDirection(QtCore.Qt.LeftToRight)
        # DockWidget.setToolTip("")
        DockWidget.setFloating(True)
        DockWidget.setFeatures(QtGui.QDockWidget.DockWidgetFloatable|QtGui.QDockWidget.DockWidgetMovable|QtGui.QDockWidget.DockWidgetClosable)
        DockWidget.setAllowedAreas(QtCore.Qt.LeftDockWidgetArea|QtCore.Qt.RightDockWidgetArea)
        self.dockWidgetContents = QtGui.QWidget()
        self.dockWidgetContents.setMaximumWidth(sizeX)
        self.dockWidgetContents.setMaximumHeight(sizeY)
        self.dockWidgetContents.setObjectName("dockWidgetContents")

        self.grid = QtGui.QGridLayout(DockWidget)
        self.grid.setSpacing(10)

        iN1 = QtGui.QLabel("Metric size")
        iN1.setAlignment(QtCore.Qt.AlignRight | QtCore.Qt.AlignVCenter)
        self.d1 = QtGui.QComboBox()
        self.d1.addItem("M2")
        self.d1.addItem("M3")
        self.d1.addItem("M4")
        self.d1.addItem("M5")
        self.d1.addItem("M6")
        self.d1.addItem("M8")
        self.d1.setCurrentIndex(1) # set M3 as default

        iN2 = QtGui.QLabel("Type")
        iN2.setAlignment(QtCore.Qt.AlignRight | QtCore.Qt.AlignVCenter)
        self.d2 = QtGui.QComboBox()
        self.d2.addItem("Hole")
        self.d2.addItem("Bolt")
        self.d2.addItem("Bolt and nut")
        self.d2.addItem("Bolt and grooved nut")
        self.d2.addItem("Bolt and washer")
        self.d2.addItem("Bolt and large washer")
        self.d2.addItem("Bolt, nut and washer")
        self.d2.addItem("Bolt, nut and large washer")
        self.d2.addItem("Bolt, grooved nut and washer")
        self.d2.addItem("Bolt, grooved nut and large washer")
        self.d2.addItem("Nut")
        self.d2.addItem("Grooved nut")
        self.d2.addItem("Nut and washer")
        self.d2.addItem("Nut and large washer")
        self.d2.addItem("Grooved nut and washer")
        self.d2.addItem("Grooved nut and large washer")
        self.d2.setCurrentIndex(1) # set "Bolt" as default
        self.d2.currentIndexChanged['QString'].connect(disableWidget)

        iN10 = QtGui.QLabel("Slot (range)")
        iN10.setAlignment(QtCore.Qt.AlignRight | QtCore.Qt.AlignVCenter)
        self.d10 = QtGui.QCheckBox()
        self.d10.setToolTip("Turn the hole into a slot")
        self.d10.stateChanged.connect(disableWidget)

        # iN11 = QtGui.QLabel("Sliding range")
        # iN11.setAlignment(QtCore.Qt.AlignRight | QtCore.Qt.AlignVCenter)
        self.d11 = QtGui.QDoubleSpinBox()
        self.d11.setValue(10.0)
        self.d11.setSingleStep(1.0)
        self.d11.setToolTip("Sliding range in with the fastener is able to move")
        self.d11.setEnabled(False)

        iN3 = QtGui.QLabel("Length")
        iN3.setAlignment(QtCore.Qt.AlignRight | QtCore.Qt.AlignVCenter)
        self.d3 = QtGui.QDoubleSpinBox()
        self.d3.setValue(20.0)
        self.d3.setSingleStep(1.0)

        iN4 = QtGui.QLabel("Groove length")
        iN4.setAlignment(QtCore.Qt.AlignRight | QtCore.Qt.AlignVCenter)
        iN4.hide() # set initial state hidden because "Bolt" mode is set
        self.d4 = QtGui.QDoubleSpinBox()
        self.d4.setValue(20.0)
        self.d4.setSingleStep(5.0)
        self.d4.setEnabled(False) # set initial state hidden because "Bolt" mode is set

        iN5 = QtGui.QLabel("Nut displacement")
        iN5.setAlignment(QtCore.Qt.AlignRight | QtCore.Qt.AlignVCenter)
        iN5.hide() # set initial state hidden because "Bolt" mode is set
        self.d5 = QtGui.QDoubleSpinBox()
        self.d5.setValue(10.0)
        self.d5.setSingleStep(1.0)
        self.d5.setEnabled(False) # set initial state hidden because "Bolt" mode is set

        iN6 = QtGui.QLabel("Tolerance")
        iN6.setAlignment(QtCore.Qt.AlignRight | QtCore.Qt.AlignVCenter)
        self.d6 = QtGui.QDoubleSpinBox()
        self.d6.setValue(0.2)
        self.d6.setSingleStep(0.1)

        iN7 = QtGui.QLabel("Color")
        iN7.setAlignment(QtCore.Qt.AlignRight | QtCore.Qt.AlignVCenter)
        self.d7 = QtGui.QComboBox()
        self.d7.addItem("Default")
        self.d7.addItem("Red")
        self.d7.addItem("Yellow")
        self.d7.addItem("Green")
        self.d7.addItem("Blue")
        self.d7.setCurrentIndex(1) # set "Red" as default

        iN8 = QtGui.QLabel("Transparency")
        iN8.setAlignment(QtCore.Qt.AlignRight | QtCore.Qt.AlignVCenter)
        self.d8 = QtGui.QSpinBox()
        self.d8.setValue(50) #Default value
        self.d8.setMaximum(100)
        self.d8.setSingleStep(10)

        iN9 = QtGui.QLabel("Group name")
        iN9.setAlignment(QtCore.Qt.AlignRight | QtCore.Qt.AlignVCenter)
        self.d9 = QtGui.QLineEdit()
        self.d9.setText("Holes") #Default value

        separator = QtGui.QFrame()
        separator.setFrameShape(QtGui.QFrame.HLine)
        separator.setLineWidth(5)

        # self.close = QtGui.QPushButton()
        # self.close.setText("Close")
        # self.close.setObjectName("close")

        self.createHole = QtGui.QPushButton()
        self.createHole.setText("Create hole")
        self.createHole.setObjectName("create")

        self.help = QtGui.QPushButton()
        self.help.setIcon(QtGui.QIcon(QtGui.QPixmap(infoIcon)))
        self.help.setFixedWidth(40)
        self.help.setObjectName("help")

        self.grid.addWidget(iN1, 0, 0)
        self.grid.addWidget(self.d1, 0, 1, 1, 2)
        self.grid.addWidget(iN2, 1, 0)
        self.grid.addWidget(self.d2, 1, 1, 1, 2)
        self.grid.addWidget(iN10, 2, 0)
        self.grid.addWidget(self.d10, 2, 1)
        # self.grid.addWidget(iN11, 3, 0)
        self.grid.addWidget(self.d11, 2, 2)
        self.grid.addWidget(iN3, 3, 0)
        self.grid.addWidget(self.d3, 3, 1, 1, 2)
        self.grid.addWidget(iN4, 4, 0)
        self.grid.addWidget(self.d4, 4, 1, 1, 2)
        self.grid.addWidget(iN5, 5, 0)
        self.grid.addWidget(self.d5, 5, 1, 1, 2)
        self.grid.addWidget(iN6, 6, 0)
        self.grid.addWidget(self.d6, 6, 1, 1, 2)
        self.grid.addWidget(iN7, 7, 0)
        self.grid.addWidget(self.d7, 7, 1, 1, 2)
        self.grid.addWidget(iN8, 8, 0)
        self.grid.addWidget(self.d8, 8, 1, 1, 2)
        self.grid.addWidget(iN9, 9, 0)
        self.grid.addWidget(self.d9, 9, 1, 1, 2)
        self.grid.addWidget(separator, 10, 0)
        self.grid.addWidget(self.help, 11, 0)
        self.grid.addWidget(self.createHole, 11, 1, 1, 2)


        # Fixed label widths
        iN1.setFixedWidth(120)

        self.dockWidgetContents.setLayout(self.grid)

        # # Set Tab order (not needed anymore because of enabling/disabling spinboxes)
        # self.dockWidgetContents.setTabOrder(self.createHole, self.d1)
        # self.dockWidgetContents.setTabOrder(self.d1, self.d2)
        # self.dockWidgetContents.setTabOrder(self.d2, self.d3)
        # self.dockWidgetContents.setTabOrder(self.d3, self.d4)
        # self.dockWidgetContents.setTabOrder(self.d4, self.d5)
        # self.dockWidgetContents.setTabOrder(self.d5, self.d6)
        # self.dockWidgetContents.setTabOrder(self.d6, self.d7)
        # self.dockWidgetContents.setTabOrder(self.d7, self.d8)
        # self.dockWidgetContents.setTabOrder(self.d8, self.createHole)

        DockWidget.setWidget(self.dockWidgetContents)


        # self.close.clicked.connect(close_dock)
        self.createHole.clicked.connect(self.onCreate)
        self.help.clicked.connect(self.onHelp)

        self.retranslateUi(DockWidget)
        QtCore.QMetaObject.connectSlotsByName(DockWidget)

## retraslateUi Qt5 compatibility ##########################################################
    def retranslateUi(self, DockWidget):
        DockWidget.setWindowTitle("Fastener holes")
        # self.close.setToolTip("Close window")
        self.help.setToolTip("More information")

### ------------------------------------------------------------------------------------ ###
### ---------code to be inserted and remove from new generation------------------------- ###
### ------------------------------------------------------------------------------------ ###

##
    def onHelp(self):
        msg="""<h1>Fastener holes</h1><p style='font-weight:normal;font-style:italic;'>version """ + __version__ + """</p><p style='font-weight:normal;'>This macro helps creating holes with tolerances so that metric fasteners can be inserted in final parts. In other words, it creates negative volumes (or holes) so that they can be use to cut another body. It makes easy and fast the creation, placement and tweaking of all needed holes.</p><p style='font-weight:normal;'>It is very useful when designing parts for 3D printing and prototyping.</p><hr style='border:1px dashed red;'><h2>Licence</h2><p style='font-weight:normal;'>Copyright 2019 Pablo Gil Fernández</p><p style='font-weight:normal;'>This work is licensed under GNU Lesser General Public License (LGPL). To view a copy of this license, visit <a href='https://www.gnu.org/licenses/lgpl-3.0.html'>https://www.gnu.org/licenses/lgpl-3.0.html</a></p>"""
        # QtGui.qApp.restoreOverrideCursor()
        # res=''
        # QtGui.qApp.restoreOverrideCursor()
        res = QtGui.QMessageBox.question(None,"Help",msg,QtGui.QMessageBox.Ok)

    def onCreate(self):
        a_clear_console()

        # ===== Variables ==============================================
        #print ("\n****** Create hole ********")

        selection = Gui.Selection.getSelection()
        selectionEx = Gui.Selection.getSelectionEx()

        if len(selectionEx) == 0:
            #print ("\n-- No selection --")
            originX = 0.0
            originY = 0.0
            originZ = 0.0
            dir = App.Vector(0.0,0.0,1.0)
            rot = pointAt(dir, App.Vector(0.0,0.0,1.0))

        elif len(selectionEx) == 1:
            #print ("\n-- 1 element selected --")
            # ------ SELECTION TYPE --------
            if selectionEx[0].SubObjects[0].ShapeType == "Vertex":
                #print ("Vertex")
                a = selection[0].Placement.inverse()
                b = selection[0].getGlobalPlacement().multiply(a)
                c = selectionEx[0].SubObjects[0].Point
                value = b.multVec(c)
                originX = value.x
                originY = value.y
                originZ = value.z
                dir = App.Vector(0.0,0.0,1.0)
                rot = pointAt(dir, App.Vector(0.0,0.0,1.0))

            elif selectionEx[0].SubObjects[0].ShapeType == "Edge":
                #print ("Line or curve")
                a = selection[0].Placement.inverse()
                b = selection[0].getGlobalPlacement().multiply(a)
                c = selectionEx[0].SubObjects[0].CenterOfMass
                value = b.multVec(c)
                originX = value.x
                originY = value.y
                originZ = value.z
                dir = App.Vector(0.0,0.0,1.0)
                rot = pointAt(dir, App.Vector(0.0,0.0,1.0))

            elif selectionEx[0].SubObjects[0].ShapeType == "Face":
                #print ("Face")
                a = selection[0].Placement.inverse()
                b = selection[0].getGlobalPlacement().multiply(a)
                c = selectionEx[0].SubObjects[0].CenterOfMass
                value = b.multVec(c)
                originX = value.x
                originY = value.y
                originZ = value.z

                dir = selectionEx[0].SubObjects[0].normalAt(0,0)

                if dir.z == 1 :
                    rot = pointAt(dir, App.Vector(0.0,1.0,0.0))
                elif dir.z == -1 :
                    rot = pointAt(dir, App.Vector(0.0,1.0,0.0))
                else :
                    rot = pointAt(dir, App.Vector(0.0,0.0,1.0))
            #else:
                #print ("\nUnknown element selected")
        else:
            #print ("\n-- More than one element selected --")
            originX = 0.0
            originY = 0.0
            originZ = 0.0
            dir = App.Vector(0.0,0.0,1.0)
            rot = pointAt(dir, App.Vector(0.0,0.0,1.0))

        #print ("\noriginX = " + str(originX))
        #print ("originY = " + str(originY))
        #print ("originZ = " + str(originZ))

        rodH = self.d3.value()
        grooveLength = self.d4.value()
        nutDisplacement = self.d5.value()
        tolerance = self.d6.value()
        bodyTransparency = self.d8.value()
        groupName = self.d9.text()

        if self.d10.isChecked():
            slot = True
        else:
            slot = False

        slotWidth = self.d11.value()

        #print (groupName)

        #print (str(self.d7.currentText()))
        if self.d7.currentText() == "Default":
            bodyColor = (0.80,0.80,0.80)
        if self.d7.currentText() == "Red":
            bodyColor = (0.67,0.00,0.00)
        if self.d7.currentText() == "Yellow":
            bodyColor = (1.00,0.92,0.03)
        if self.d7.currentText() == "Green":
            bodyColor = (0.33,0.67,0.00)
        if self.d7.currentText() == "Blue":
            bodyColor = (0.00,0.33,1.00)

        #print (str(self.d1.currentText()))
        if self.d1.currentText() == "M2":
            headR = 1.90 + tolerance
            headH = 2.20 + tolerance
            bodyR = 1.00 + tolerance
            bodyH = rodH + tolerance
            nutH = 1.80 + tolerance
            nutWidth = 4.00 + tolerance * 2
            washerR = 2.45 + tolerance
            washerH = 0.30 + tolerance
            washerLargeR = rodH + tolerance # does not exist
            washerLargeH = rodH + tolerance # does not exist
        if self.d1.currentText() == "M3":
            headR = 2.80 + tolerance
            headH = 3.20 + tolerance
            bodyR = 1.50 + tolerance
            bodyH = rodH + tolerance
            nutH = 2.50 + tolerance
            nutWidth = 5.40 + tolerance * 2
            washerR = 3.40 + tolerance
            washerH = 0.40 + tolerance
            washerLargeR = 4.50 + tolerance
            washerLargeH = 0.70 + tolerance
        if self.d1.currentText() == "M4":
            headR = 3.60 + tolerance
            headH = 4.20 + tolerance
            bodyR = 2.00 + tolerance
            bodyH = rodH + tolerance
            nutH = 3.20 + tolerance
            nutWidth = 6.90 + tolerance * 2
            washerR = 4.50 + tolerance
            washerH = 0.80 + tolerance
            washerLargeR = 5.90 + tolerance
            washerLargeH = 1.00 + tolerance
        if self.d1.currentText() == "M5":
            headR = 4.40 + tolerance
            headH = 5.20 + tolerance
            bodyR = 2.50 + tolerance
            bodyH = rodH + tolerance
            nutH = 4.20 + tolerance
            nutWidth = 8.00 + tolerance * 2
            washerR = 4.90 + tolerance
            washerH = 0.90 + tolerance
            washerLargeR = 7.35 + tolerance
            washerLargeH = 1.25 + tolerance
        if self.d1.currentText() == "M6":
            headR = 5.20 + tolerance
            headH = 6.20 + tolerance
            bodyR = 3.0 + tolerance
            bodyH = rodH + tolerance
            nutH = 4.90 + tolerance
            nutWidth = 10.00 + tolerance * 2
            washerR = 6.00 + tolerance
            washerH = 1.80 + tolerance
            washerLargeR = 9.00 + tolerance
            washerLargeH = 1.80 + tolerance
        if self.d1.currentText() == "M8":
            headR = 6.75 + tolerance
            headH = 8.20 + tolerance
            bodyR = 4.00 + tolerance
            bodyH = rodH + tolerance
            nutH = 7.20 + tolerance
            nutWidth = 13.00 + tolerance * 2
            washerR = 8.00 + tolerance
            washerH = 1.80 + tolerance
            washerLargeR = 12.00 + tolerance
            washerLargeH = 2.20 + tolerance

        # Creates group called "Holes" if it doesn't exist
        if len(App.ActiveDocument.getObjectsByLabel(groupName)) == 0:
            App.ActiveDocument.addObject("App::DocumentObjectGroup",groupName)

    # ===== Hole ==============================================
        if self.d2.currentText() == "Hole" and slot == False:
            body = App.ActiveDocument.addObject("PartDesign::Body",self.d1.currentText() + ' Hole')
            Gui.activeView().setActiveObject('pdbody', body)
            App.ActiveDocument.recompute()

            cylinder1 = App.ActiveDocument.addObject("PartDesign::AdditiveCylinder","Cylinder1")
            body.addObject(cylinder1)
            cylinder1.Radius = bodyR
            cylinder1.Height = rodH
            cylinder1.Label = "Hole"
            cylinder1.AttachmentOffset = App.Placement(App.Vector(0.0, 0.0, 0.0),  App.Rotation(0.0, 0.0, 0.0))
            cylinder1.MapReversed = True
            cylinder1.Support = [(App.activeDocument().XY_Plane,'')]
            cylinder1.MapMode = 'FlatFace'

            body.Placement.Base = App.Vector(originX, originY, originZ)
            body.Placement.Rotation = rot.Q

            Gui.activeDocument().activeObject().ShapeColor = bodyColor
            Gui.activeDocument().activeObject().Transparency = bodyTransparency
            Gui.activeView().setActiveObject('pdbody', None)
            App.ActiveDocument.getObject(groupName).addObject(body)
            App.ActiveDocument.recompute()

            #print ("\n" + self.d1.currentText() + " Hole created")

    # ===== Hole (slot)==============================================
        if self.d2.currentText() == "Hole" and slot == True:
            body = App.ActiveDocument.addObject("PartDesign::Body",self.d1.currentText() + ' Hole with slot')
            Gui.activeView().setActiveObject('pdbody', body)
            App.ActiveDocument.recompute()

            cylinder1 = App.ActiveDocument.addObject("PartDesign::AdditiveCylinder","Cylinder1")
            body.addObject(cylinder1)
            cylinder1.Radius = bodyR
            cylinder1.Height = rodH
            cylinder1.Label = "Hole"
            cylinder1.AttachmentOffset = App.Placement(App.Vector(slotWidth/2, 0.0, 0.0),  App.Rotation(0.0, 0.0, 0.0))
            cylinder1.MapReversed = True
            cylinder1.Support = [(App.activeDocument().XY_Plane,'')]
            cylinder1.MapMode = 'FlatFace'

            cube = App.ActiveDocument.addObject("PartDesign::AdditiveBox","Cube")
            body.addObject(cube)
            cube.Length = slotWidth
            cube.Width = bodyR*2
            cube.Height = rodH
            cube.Label = "slot"
            cube.AttachmentOffset = App.Placement(App.Vector(-slotWidth/2, -bodyR, -rodH),  App.Rotation(0.0, 0.0, 0.0))
            cube.MapReversed = False
            cube.Support = [(App.activeDocument().XY_Plane,'')]
            cube.MapMode = 'FlatFace'

            cylinder2 = App.ActiveDocument.addObject("PartDesign::AdditiveCylinder","Cylinder1")
            body.addObject(cylinder2)
            cylinder2.Radius = bodyR
            cylinder2.Height = rodH
            cylinder2.Label = "Hole"
            cylinder2.AttachmentOffset = App.Placement(App.Vector(-slotWidth/2, 0.0, 0.0),  App.Rotation(0.0, 0.0, 0.0))
            cylinder2.MapReversed = True
            cylinder2.Support = [(App.activeDocument().XY_Plane,'')]
            cylinder2.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            #print ("\n" + self.d1.currentText() + " Hole created")

    # ===== Bolt ==============================================
        if self.d2.currentText() == "Bolt" and slot == False:
            body = App.ActiveDocument.addObject("PartDesign::Body",self.d1.currentText() + ' Bolt')
            Gui.activeView().setActiveObject('pdbody', body)

            cylinder1 = App.ActiveDocument.addObject("PartDesign::AdditiveCylinder","Cylinder1")
            body.addObject(cylinder1)
            cylinder1.Radius = headR
            cylinder1.Height = headH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cylinder2 = App.ActiveDocument.addObject("PartDesign::AdditiveCylinder","Cylinder2")
            body.addObject(cylinder2)
            cylinder2.Radius = bodyR
            cylinder2.Height = bodyH + headH
            cylinder2.Label = "Body"
            cylinder2.AttachmentOffset = App.Placement(App.Vector(0.0, 0.0, 0.0),  App.Rotation(0.0, 0.0, 180.0))
            cylinder2.MapReversed = False
            cylinder2.Support = [(App.activeDocument().XY_Plane,'')]
            cylinder2.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            #print ("\n" + self.d1.currentText() + " Bolt created")

    # ===== Bolt (slot) ==============================================
        if self.d2.currentText() == "Bolt" and slot == True:
            body = App.ActiveDocument.addObject("PartDesign::Body",self.d1.currentText() + ' Bolt with slot')
            Gui.activeView().setActiveObject('pdbody', body)
            App.ActiveDocument.recompute()

            cylinder1 = App.ActiveDocument.addObject("PartDesign::AdditiveCylinder","Cylinder1")
            body.addObject(cylinder1)
            cylinder1.Radius = headR
            cylinder1.Height = headH
            cylinder1.Label = "Head-left"
            cylinder1.AttachmentOffset = App.Placement(App.Vector(slotWidth/2, 0.0, 0.0),  App.Rotation(0.0, 0.0, 0.0))
            cylinder1.MapReversed = True
            cylinder1.Support = [(App.activeDocument().XY_Plane,'')]
            cylinder1.MapMode = 'FlatFace'

            cube1 = App.ActiveDocument.addObject("PartDesign::AdditiveBox","Cube")
            body.addObject(cube1)
            cube1.Length = slotWidth
            cube1.Width = headR*2
            cube1.Height = headH
            cube1.Label = "Head-center"
            cube1.AttachmentOffset = App.Placement(App.Vector(-slotWidth/2, -headR, -headH),  App.Rotation(0.0, 0.0, 0.0))
            cube1.MapReversed = False
            cube1.Support = [(App.activeDocument().XY_Plane,'')]
            cube1.MapMode = 'FlatFace'

            cylinder2 = App.ActiveDocument.addObject("PartDesign::AdditiveCylinder","Cylinder1")
            body.addObject(cylinder2)
            cylinder2.Radius = headR
            cylinder2.Height = headH
            cylinder2.Label = "Head-right"
            cylinder2.AttachmentOffset = App.Placement(App.Vector(-slotWidth/2, 0.0, 0.0),  App.Rotation(0.0, 0.0, 0.0))
            cylinder2.MapReversed = True
            cylinder2.Support = [(App.activeDocument().XY_Plane,'')]
            cylinder2.MapMode = 'FlatFace'

            cylinder3 = App.ActiveDocument.addObject("PartDesign::AdditiveCylinder","Cylinder1")
            body.addObject(cylinder3)
            cylinder3.Radius = bodyR
            cylinder3.Height = bodyH + headH
            cylinder3.Label = "Body-left"
            cylinder3.AttachmentOffset = App.Placement(App.Vector(slotWidth/2, 0.0, 0.0),  App.Rotation(0.0, 0.0, 0.0))
            cylinder3.MapReversed = True
            cylinder3.Support = [(App.activeDocument().XY_Plane,'')]
            cylinder3.MapMode = 'FlatFace'

            cube2 = App.ActiveDocument.addObject("PartDesign::AdditiveBox","Cube")
            body.addObject(cube2)
            cube2.Length = slotWidth
            cube2.Width = bodyR*2
            cube2.Height = bodyH + headH
            cube2.Label = "Body-center"
            cube2.AttachmentOffset = App.Placement(App.Vector(-slotWidth/2, -bodyR, -bodyH - headH),  App.Rotation(0.0, 0.0, 0.0))
            cube2.MapReversed = False
            cube2.Support = [(App.activeDocument().XY_Plane,'')]
            cube2.MapMode = 'FlatFace'

            cylinder4 = App.ActiveDocument.addObject("PartDesign::AdditiveCylinder","Cylinder1")
            body.addObject(cylinder4)
            cylinder4.Radius = bodyR
            cylinder4.Height = bodyH + headH
            cylinder4.Label = "Body-right"
            cylinder4.AttachmentOffset = App.Placement(App.Vector(-slotWidth/2, 0.0, 0.0),  App.Rotation(0.0, 0.0, 0.0))
            cylinder4.MapReversed = True
            cylinder4.Support = [(App.activeDocument().XY_Plane,'')]
            cylinder4.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            #print ("\n" + self.d1.currentText() + " Bolt created")

    # ===== Bolt and nut ==============================================
        elif self.d2.currentText() == "Bolt and nut" and slot == False:
            body = App.ActiveDocument.addObject("PartDesign::Body",self.d1.currentText() + ' Bolt and nut')
            Gui.activeView().setActiveObject('pdbody', body)

            cylinder1 = App.ActiveDocument.addObject("PartDesign::AdditiveCylinder","Cylinder1")
            body.addObject(cylinder1)
            cylinder1.Radius = headR
            cylinder1.Height = headH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cylinder2 = App.ActiveDocument.addObject("PartDesign::AdditiveCylinder","Cylinder2")
            body.addObject(cylinder2)
            cylinder2.Radius = bodyR
            cylinder2.Height = bodyH + headH
            cylinder2.Label = "Body"
            cylinder2.AttachmentOffset = App.Placement(App.Vector(0.0, 0.0, 0.0),  App.Rotation(0.0, 0.0, 180.0))
            cylinder2.MapReversed = False
            cylinder2.Support = [(App.activeDocument().XY_Plane,'')]
            cylinder2.MapMode = 'FlatFace'

            prism = App.ActiveDocument.addObject('PartDesign::AdditivePrism','Prism')
            body.addObject(prism)
            prism.Polygon = 6
            prism.Circumradius = nutWidth / 2 / cos(math.radians(180/float(6)))
            prism.Height = nutH
            prism.Label = "Nut"
            prism.AttachmentOffset = App.Placement(App.Vector(0.0, 0.0, -nutDisplacement),  App.Rotation(0.0, 0.0, 0.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Bolt and nut created")

    # ===== Bolt and nut (slot)==============================================
        if self.d2.currentText() == "Bolt and nut" and slot == True:
            body = App.ActiveDocument.addObject("PartDesign::Body",self.d1.currentText() + ' Bolt and nut with slot')
            Gui.activeView().setActiveObject('pdbody', body)
            App.ActiveDocument.recompute()

            cylinder1 = App.ActiveDocument.addObject("PartDesign::AdditiveCylinder","Cylinder1")
            body.addObject(cylinder1)
            cylinder1.Radius = headR
            cylinder1.Height = headH
            cylinder1.Label = "Head-left"
            cylinder1.AttachmentOffset = App.Placement(App.Vector(slotWidth/2, 0.0, 0.0),  App.Rotation(0.0, 0.0, 0.0))
            cylinder1.MapReversed = True
            cylinder1.Support = [(App.activeDocument().XY_Plane,'')]
            cylinder1.MapMode = 'FlatFace'

            cube1 = App.ActiveDocument.addObject("PartDesign::AdditiveBox","Cube")
            body.addObject(cube1)
            cube1.Length = slotWidth
            cube1.Width = headR*2
            cube1.Height = headH
            cube1.Label = "Head-center"
            cube1.AttachmentOffset = App.Placement(App.Vector(-slotWidth/2, -headR, -headH),  App.Rotation(0.0, 0.0, 0.0))
            cube1.MapReversed = False
            cube1.Support = [(App.activeDocument().XY_Plane,'')]
            cube1.MapMode = 'FlatFace'

            cylinder2 = App.ActiveDocument.addObject("PartDesign::AdditiveCylinder","Cylinder1")
            body.addObject(cylinder2)
            cylinder2.Radius = headR
            cylinder2.Height = headH
            cylinder2.Label = "Head-right"
            cylinder2.AttachmentOffset = App.Placement(App.Vector(-slotWidth/2, 0.0, 0.0),  App.Rotation(0.0, 0.0, 0.0))
            cylinder2.MapReversed = True
            cylinder2.Support = [(App.activeDocument().XY_Plane,'')]
            cylinder2.MapMode = 'FlatFace'

            cylinder3 = App.ActiveDocument.addObject("PartDesign::AdditiveCylinder","Cylinder1")
            body.addObject(cylinder3)
            cylinder3.Radius = bodyR
            cylinder3.Height = bodyH + headH
            cylinder3.Label = "Body-left"
            cylinder3.AttachmentOffset = App.Placement(App.Vector(slotWidth/2, 0.0, 0.0),  App.Rotation(0.0, 0.0, 0.0))
            cylinder3.MapReversed = True
            cylinder3.Support = [(App.activeDocument().XY_Plane,'')]
            cylinder3.MapMode = 'FlatFace'

            cube2 = App.ActiveDocument.addObject("PartDesign::AdditiveBox","Cube")
            body.addObject(cube2)
            cube2.Length = slotWidth
            cube2.Width = bodyR*2
            cube2.Height = bodyH + headH
            cube2.Label = "Body-center"
            cube2.AttachmentOffset = App.Placement(App.Vector(-slotWidth/2, -bodyR, -bodyH - headH),  App.Rotation(0.0, 0.0, 0.0))
            cube2.MapReversed = False
            cube2.Support = [(App.activeDocument().XY_Plane,'')]
            cube2.MapMode = 'FlatFace'

            cylinder4 = App.ActiveDocument.addObject("PartDesign::AdditiveCylinder","Cylinder1")
            body.addObject(cylinder4)
            cylinder4.Radius = bodyR
            cylinder4.Height = bodyH + headH
            cylinder4.Label = "Body-right"
            cylinder4.AttachmentOffset = App.Placement(App.Vector(-slotWidth/2, 0.0, 0.0),  App.Rotation(0.0, 0.0, 0.0))
            cylinder4.MapReversed = True
            cylinder4.Support = [(App.activeDocument().XY_Plane,'')]
            cylinder4.MapMode = 'FlatFace'

            prism1 = App.ActiveDocument.addObject('PartDesign::AdditivePrism','Prism')
            body.addObject(prism1)
            prism1.Polygon = 6
            prism1.Circumradius = nutWidth / 2 / cos(math.radians(180/float(6)))
            prism1.Height = nutH
            prism1.Label = "Nut-left"
            prism1.AttachmentOffset = App.Placement(App.Vector(slotWidth/2, 0.0, -nutDisplacement),  App.Rotation(0.0, 0.0, 0.0))
            prism1.MapReversed = False
            prism1.Support = [(App.activeDocument().XY_Plane,'')]
            prism1.MapMode = 'FlatFace'

            cube3 = App.ActiveDocument.addObject("PartDesign::AdditiveBox","Cube")
            body.addObject(cube3)
            cube3.Length = slotWidth
            cube3.Width = nutWidth
            cube3.Height = nutH
            cube3.Label = "Nut-center"
            cube3.AttachmentOffset = App.Placement(App.Vector(-slotWidth/2, -nutWidth/2, -nutDisplacement),  App.Rotation(0.0, 0.0, 0.0))
            cube3.MapReversed = False
            cube3.Support = [(App.activeDocument().XY_Plane,'')]
            cube3.MapMode = 'FlatFace'

            prism2 = App.ActiveDocument.addObject('PartDesign::AdditivePrism','Prism')
            body.addObject(prism2)
            prism2.Polygon = 6
            prism2.Circumradius = nutWidth / 2 / cos(math.radians(180/float(6)))
            prism2.Height = nutH
            prism2.Label = "Nut-right"
            prism2.AttachmentOffset = App.Placement(App.Vector(-slotWidth/2, 0.0, -nutDisplacement),  App.Rotation(0.0, 0.0, 0.0))
            prism2.MapReversed = False
            prism2.Support = [(App.activeDocument().XY_Plane,'')]
            prism2.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            #print ("\n" + self.d1.currentText() + " Bolt and nut with slot created")

    # ===== Bolt and grooved nut ==============================================
        elif self.d2.currentText() == "Bolt and grooved nut" and slot == False:
            body = App.ActiveDocument.addObject("PartDesign::Body",self.d1.currentText() + ' Bolt and nut')
            Gui.activeView().setActiveObject('pdbody', body)

            cylinder1 = App.ActiveDocument.addObject("PartDesign::AdditiveCylinder","Cylinder1")
            body.addObject(cylinder1)
            cylinder1.Radius = headR
            cylinder1.Height = headH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cylinder2 = App.ActiveDocument.addObject("PartDesign::AdditiveCylinder","Cylinder2")
            body.addObject(cylinder2)
            cylinder2.Radius = bodyR
            cylinder2.Height = bodyH + headH
            cylinder2.Label = "Body"
            cylinder2.AttachmentOffset = App.Placement(App.Vector(0.0, 0.0, 0.0),  App.Rotation(0.0, 0.0, 180.0))
            cylinder2.MapReversed = False
            cylinder2.Support = [(App.activeDocument().XY_Plane,'')]
            cylinder2.MapMode = 'FlatFace'

            cube = App.ActiveDocument.addObject("PartDesign::AdditiveBox","Cube")
            body.addObject(cube)
            cube.Length = grooveLength
            cube.Width = nutWidth
            cube.Height = nutH
            cube.Label = "Groove"
            cube.AttachmentOffset = App.Placement(App.Vector(0.0, -cube.Width/2,-nutDisplacement),  App.Rotation(0.0, 0.0, 0.0))
            cube.MapReversed = False
            cube.Support = [(App.activeDocument().XY_Plane,'')]
            cube.MapMode = 'FlatFace'

            prism = App.ActiveDocument.addObject("PartDesign::AdditivePrism","Prism")
            body.addObject(prism)
            prism.Polygon = 6
            prism.Circumradius = nutWidth / 2 / cos(math.radians(180/float(6)))
            prism.Height = nutH
            prism.Label = "Nut"
            prism.AttachmentOffset = App.Placement(App.Vector(0.0, 0.0, -nutDisplacement),  App.Rotation(0.0, 0.0, 0.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Bolt and grooved nut created")

    # ===== Bolt and washer ==============================================
        elif self.d2.currentText() == "Bolt and washer" and slot == False:
            body = App.ActiveDocument.addObject("PartDesign::Body",self.d1.currentText() + ' Bolt and washer')
            Gui.activeView().setActiveObject('pdbody', body)

            cylinder1 = App.ActiveDocument.addObject("PartDesign::AdditiveCylinder","Cylinder1")
            body.addObject(cylinder1)
            cylinder1.Radius = washerR
            cylinder1.Height = headH + washerH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cylinder2 = App.ActiveDocument.addObject("PartDesign::AdditiveCylinder","Cylinder2")
            body.addObject(cylinder2)
            cylinder2.Radius = bodyR
            cylinder2.Height = bodyH + headH + washerH
            cylinder2.Label = "Body"
            cylinder2.AttachmentOffset = App.Placement(App.Vector(0.0, 0.0, 0.0),  App.Rotation(0.0, 0.0, 180.0))
            cylinder2.MapReversed = False
            cylinder2.Support = [(App.activeDocument().XY_Plane,'')]
            cylinder2.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Bolt and washer created")

    # ===== Bolt and washer (slot) ==============================================
        if self.d2.currentText() == "Bolt and washer" and slot == True:
            body = App.ActiveDocument.addObject("PartDesign::Body",self.d1.currentText() + ' Bolt and washer with slot')
            Gui.activeView().setActiveObject('pdbody', body)
            App.ActiveDocument.recompute()

            cylinder1 = App.ActiveDocument.addObject("PartDesign::AdditiveCylinder","Cylinder1")
            body.addObject(cylinder1)
            cylinder1.Radius = washerR
            cylinder1.Height = headH + washerH
            cylinder1.Label = "Head-left"
            cylinder1.AttachmentOffset = App.Placement(App.Vector(slotWidth/2, 0.0, 0.0),  App.Rotation(0.0, 0.0, 0.0))
            cylinder1.MapReversed = True
            cylinder1.Support = [(App.activeDocument().XY_Plane,'')]
            cylinder1.MapMode = 'FlatFace'

            cube1 = App.ActiveDocument.addObject("PartDesign::AdditiveBox","Cube")
            body.addObject(cube1)
            cube1.Length = slotWidth
            cube1.Width = washerR*2
            cube1.Height = headH + washerH
            cube1.Label = "Head-center"
            cube1.AttachmentOffset = App.Placement(App.Vector(-slotWidth/2, -washerR, -headH -washerH),  App.Rotation(0.0, 0.0, 0.0))
            cube1.MapReversed = False
            cube1.Support = [(App.activeDocument().XY_Plane,'')]
            cube1.MapMode = 'FlatFace'

            cylinder2 = App.ActiveDocument.addObject("PartDesign::AdditiveCylinder","Cylinder1")
            body.addObject(cylinder2)
            cylinder2.Radius = washerR
            cylinder2.Height = headH + washerH
            cylinder2.Label = "Head-right"
            cylinder2.AttachmentOffset = App.Placement(App.Vector(-slotWidth/2, 0.0, 0.0),  App.Rotation(0.0, 0.0, 0.0))
            cylinder2.MapReversed = True
            cylinder2.Support = [(App.activeDocument().XY_Plane,'')]
            cylinder2.MapMode = 'FlatFace'

            cylinder3 = App.ActiveDocument.addObject("PartDesign::AdditiveCylinder","Cylinder1")
            body.addObject(cylinder3)
            cylinder3.Radius = bodyR
            cylinder3.Height = bodyH + headH + washerH
            cylinder3.Label = "Body-left"
            cylinder3.AttachmentOffset = App.Placement(App.Vector(slotWidth/2, 0.0, 0.0),  App.Rotation(0.0, 0.0, 0.0))
            cylinder3.MapReversed = True
            cylinder3.Support = [(App.activeDocument().XY_Plane,'')]
            cylinder3.MapMode = 'FlatFace'

            cube2 = App.ActiveDocument.addObject("PartDesign::AdditiveBox","Cube")
            body.addObject(cube2)
            cube2.Length = slotWidth
            cube2.Width = bodyR*2
            cube2.Height = bodyH + headH + washerH
            cube2.Label = "Body-center"
            cube2.AttachmentOffset = App.Placement(App.Vector(-slotWidth/2, -bodyR, -bodyH - headH - washerH),  App.Rotation(0.0, 0.0, 0.0))
            cube2.MapReversed = False
            cube2.Support = [(App.activeDocument().XY_Plane,'')]
            cube2.MapMode = 'FlatFace'

            cylinder4 = App.ActiveDocument.addObject("PartDesign::AdditiveCylinder","Cylinder1")
            body.addObject(cylinder4)
            cylinder4.Radius = bodyR
            cylinder4.Height = bodyH + headH + washerH
            cylinder4.Label = "Body-right"
            cylinder4.AttachmentOffset = App.Placement(App.Vector(-slotWidth/2, 0.0, 0.0),  App.Rotation(0.0, 0.0, 0.0))
            cylinder4.MapReversed = True
            cylinder4.Support = [(App.activeDocument().XY_Plane,'')]
            cylinder4.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            #print ("\n" + self.d1.currentText() + " Bolt and washer with slot created")

    # ===== Bolt and large washer ==============================================
        elif self.d2.currentText() == "Bolt and large washer" and slot == False:
            body = App.ActiveDocument.addObject("PartDesign::Body",self.d1.currentText() + ' Bolt and large washer')
            Gui.activeView().setActiveObject('pdbody', body)

            cylinder1 = App.ActiveDocument.addObject("PartDesign::AdditiveCylinder","Cylinder1")
            body.addObject(cylinder1)
            cylinder1.Radius = washerLargeR
            cylinder1.Height = headH + washerLargeH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cylinder2 = App.ActiveDocument.addObject("PartDesign::AdditiveCylinder","Cylinder2")
            body.addObject(cylinder2)
            cylinder2.Radius = bodyR
            cylinder2.Height = bodyH + headH + washerLargeH
            cylinder2.Label = "Body"
            cylinder2.AttachmentOffset = App.Placement(App.Vector(0.0, 0.0, 0.0),  App.Rotation(0.0, 0.0, 180.0))
            cylinder2.MapReversed = False
            cylinder2.Support = [(App.activeDocument().XY_Plane,'')]
            cylinder2.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Bolt and large washer created")

    # ===== Bolt and large washer (slot) ==============================================
        if self.d2.currentText() == "Bolt and large washer" and slot == True:
            body = App.ActiveDocument.addObject("PartDesign::Body",self.d1.currentText() + ' Bolt and large washer with slot')
            Gui.activeView().setActiveObject('pdbody', body)
            App.ActiveDocument.recompute()

            cylinder1 = App.ActiveDocument.addObject("PartDesign::AdditiveCylinder","Cylinder1")
            body.addObject(cylinder1)
            cylinder1.Radius = washerLargeR
            cylinder1.Height = headH + washerLargeH
            cylinder1.Label = "Head-left"
            cylinder1.AttachmentOffset = App.Placement(App.Vector(slotWidth/2, 0.0, 0.0),  App.Rotation(0.0, 0.0, 0.0))
            cylinder1.MapReversed = True
            cylinder1.Support = [(App.activeDocument().XY_Plane,'')]
            cylinder1.MapMode = 'FlatFace'

            cube1 = App.ActiveDocument.addObject("PartDesign::AdditiveBox","Cube")
            body.addObject(cube1)
            cube1.Length = slotWidth
            cube1.Width = washerLargeR*2
            cube1.Height = headH + washerLargeH
            cube1.Label = "Head-center"
            cube1.AttachmentOffset = App.Placement(App.Vector(-slotWidth/2, -washerLargeR, -headH -washerLargeH),  App.Rotation(0.0, 0.0, 0.0))
            cube1.MapReversed = False
            cube1.Support = [(App.activeDocument().XY_Plane,'')]
            cube1.MapMode = 'FlatFace'

            cylinder2 = App.ActiveDocument.addObject("PartDesign::AdditiveCylinder","Cylinder1")
            body.addObject(cylinder2)
            cylinder2.Radius = washerLargeR
            cylinder2.Height = headH + washerLargeH
            cylinder2.Label = "Head-right"
            cylinder2.AttachmentOffset = App.Placement(App.Vector(-slotWidth/2, 0.0, 0.0),  App.Rotation(0.0, 0.0, 0.0))
            cylinder2.MapReversed = True
            cylinder2.Support = [(App.activeDocument().XY_Plane,'')]
            cylinder2.MapMode = 'FlatFace'

            cylinder3 = App.ActiveDocument.addObject("PartDesign::AdditiveCylinder","Cylinder1")
            body.addObject(cylinder3)
            cylinder3.Radius = bodyR
            cylinder3.Height = bodyH + headH + washerLargeH
            cylinder3.Label = "Body-left"
            cylinder3.AttachmentOffset = App.Placement(App.Vector(slotWidth/2, 0.0, 0.0),  App.Rotation(0.0, 0.0, 0.0))
            cylinder3.MapReversed = True
            cylinder3.Support = [(App.activeDocument().XY_Plane,'')]
            cylinder3.MapMode = 'FlatFace'

            cube2 = App.ActiveDocument.addObject("PartDesign::AdditiveBox","Cube")
            body.addObject(cube2)
            cube2.Length = slotWidth
            cube2.Width = bodyR*2
            cube2.Height = bodyH + headH + washerLargeH
            cube2.Label = "Body-center"
            cube2.AttachmentOffset = App.Placement(App.Vector(-slotWidth/2, -bodyR, -bodyH - headH - washerLargeH),  App.Rotation(0.0, 0.0, 0.0))
            cube2.MapReversed = False
            cube2.Support = [(App.activeDocument().XY_Plane,'')]
            cube2.MapMode = 'FlatFace'

            cylinder4 = App.ActiveDocument.addObject("PartDesign::AdditiveCylinder","Cylinder1")
            body.addObject(cylinder4)
            cylinder4.Radius = bodyR
            cylinder4.Height = bodyH + headH + washerLargeH
            cylinder4.Label = "Body-right"
            cylinder4.AttachmentOffset = App.Placement(App.Vector(-slotWidth/2, 0.0, 0.0),  App.Rotation(0.0, 0.0, 0.0))
            cylinder4.MapReversed = True
            cylinder4.Support = [(App.activeDocument().XY_Plane,'')]
            cylinder4.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            #print ("\n" + self.d1.currentText() + " Bolt and large washer with slot created")

    # ===== Bolt, nut and washer ==============================================
        elif self.d2.currentText() == "Bolt, nut and washer" and slot == False:
            body = App.ActiveDocument.addObject("PartDesign::Body",self.d1.currentText() + ' Bolt nut and washer')
            Gui.activeView().setActiveObject('pdbody', body)

            cylinder1 = App.ActiveDocument.addObject("PartDesign::AdditiveCylinder","Cylinder1")
            body.addObject(cylinder1)
            cylinder1.Radius = washerR
            cylinder1.Height = headH + washerH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cylinder2 = App.ActiveDocument.addObject("PartDesign::AdditiveCylinder","Cylinder2")
            body.addObject(cylinder2)
            cylinder2.Radius = bodyR
            cylinder2.Height = bodyH + headH + washerH
            cylinder2.Label = "Body"
            cylinder2.AttachmentOffset = App.Placement(App.Vector(0.0, 0.0, 0.0),  App.Rotation(0.0, 0.0, 180.0))
            cylinder2.MapReversed = False
            cylinder2.Support = [(App.activeDocument().XY_Plane,'')]
            cylinder2.MapMode = 'FlatFace'

            prism = App.ActiveDocument.addObject("PartDesign::AdditivePrism","Prism")
            body.addObject(prism)
            prism.Polygon = 6
            prism.Circumradius = headR
            prism.Height = nutH
            prism.Label = "Nut"
            prism.AttachmentOffset = App.Placement(App.Vector(0.0, 0.0, -nutDisplacement),  App.Rotation(0.0, 0.0, 0.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Bolt, nut and washer created")

    # ===== Bolt, nut and washer (slot) ==============================================
        if self.d2.currentText() == "Bolt, nut and washer" and slot == True:
            body = App.ActiveDocument.addObject("PartDesign::Body",self.d1.currentText() + ' Bolt nut and washer with slot')
            Gui.activeView().setActiveObject('pdbody', body)
            App.ActiveDocument.recompute()

            cylinder1 = App.ActiveDocument.addObject("PartDesign::AdditiveCylinder","Cylinder1")
            body.addObject(cylinder1)
            cylinder1.Radius = washerR
            cylinder1.Height = headH + washerH
            cylinder1.Label = "Head-left"
            cylinder1.AttachmentOffset = App.Placement(App.Vector(slotWidth/2, 0.0, 0.0),  App.Rotation(0.0, 0.0, 0.0))
            cylinder1.MapReversed = True
            cylinder1.Support = [(App.activeDocument().XY_Plane,'')]
            cylinder1.MapMode = 'FlatFace'

            cube1 = App.ActiveDocument.addObject("PartDesign::AdditiveBox","Cube")
            body.addObject(cube1)
            cube1.Length = slotWidth
            cube1.Width = washerR*2
            cube1.Height = headH + washerH
            cube1.Label = "Head-center"
            cube1.AttachmentOffset = App.Placement(App.Vector(-slotWidth/2, -washerR, -headH -washerH),  App.Rotation(0.0, 0.0, 0.0))
            cube1.MapReversed = False
            cube1.Support = [(App.activeDocument().XY_Plane,'')]
            cube1.MapMode = 'FlatFace'

            cylinder2 = App.ActiveDocument.addObject("PartDesign::AdditiveCylinder","Cylinder1")
            body.addObject(cylinder2)
            cylinder2.Radius = washerR
            cylinder2.Height = headH + washerH
            cylinder2.Label = "Head-right"
            cylinder2.AttachmentOffset = App.Placement(App.Vector(-slotWidth/2, 0.0, 0.0),  App.Rotation(0.0, 0.0, 0.0))
            cylinder2.MapReversed = True
            cylinder2.Support = [(App.activeDocument().XY_Plane,'')]
            cylinder2.MapMode = 'FlatFace'

            cylinder3 = App.ActiveDocument.addObject("PartDesign::AdditiveCylinder","Cylinder1")
            body.addObject(cylinder3)
            cylinder3.Radius = bodyR
            cylinder3.Height = bodyH + headH + washerH
            cylinder3.Label = "Body-left"
            cylinder3.AttachmentOffset = App.Placement(App.Vector(slotWidth/2, 0.0, 0.0),  App.Rotation(0.0, 0.0, 0.0))
            cylinder3.MapReversed = True
            cylinder3.Support = [(App.activeDocument().XY_Plane,'')]
            cylinder3.MapMode = 'FlatFace'

            cube2 = App.ActiveDocument.addObject("PartDesign::AdditiveBox","Cube")
            body.addObject(cube2)
            cube2.Length = slotWidth
            cube2.Width = bodyR*2
            cube2.Height = bodyH + headH + washerH
            cube2.Label = "Body-center"
            cube2.AttachmentOffset = App.Placement(App.Vector(-slotWidth/2, -bodyR, -bodyH - headH - washerH),  App.Rotation(0.0, 0.0, 0.0))
            cube2.MapReversed = False
            cube2.Support = [(App.activeDocument().XY_Plane,'')]
            cube2.MapMode = 'FlatFace'

            cylinder4 = App.ActiveDocument.addObject("PartDesign::AdditiveCylinder","Cylinder1")
            body.addObject(cylinder4)
            cylinder4.Radius = bodyR
            cylinder4.Height = bodyH + headH + washerH
            cylinder4.Label = "Body-right"
            cylinder4.AttachmentOffset = App.Placement(App.Vector(-slotWidth/2, 0.0, 0.0),  App.Rotation(0.0, 0.0, 0.0))
            cylinder4.MapReversed = True
            cylinder4.Support = [(App.activeDocument().XY_Plane,'')]
            cylinder4.MapMode = 'FlatFace'

            prism1 = App.ActiveDocument.addObject('PartDesign::AdditivePrism','Prism')
            body.addObject(prism1)
            prism1.Polygon = 6
            prism1.Circumradius = nutWidth / 2 / cos(math.radians(180/float(6)))
            prism1.Height = nutH
            prism1.Label = "Nut-left"
            prism1.AttachmentOffset = App.Placement(App.Vector(slotWidth/2, 0.0, -nutDisplacement),  App.Rotation(0.0, 0.0, 0.0))
            prism1.MapReversed = False
            prism1.Support = [(App.activeDocument().XY_Plane,'')]
            prism1.MapMode = 'FlatFace'

            cube3 = App.ActiveDocument.addObject("PartDesign::AdditiveBox","Cube")
            body.addObject(cube3)
            cube3.Length = slotWidth
            cube3.Width = nutWidth
            cube3.Height = nutH
            cube3.Label = "Nut-center"
            cube3.AttachmentOffset = App.Placement(App.Vector(-slotWidth/2, -nutWidth/2, -nutDisplacement),  App.Rotation(0.0, 0.0, 0.0))
            cube3.MapReversed = False
            cube3.Support = [(App.activeDocument().XY_Plane,'')]
            cube3.MapMode = 'FlatFace'

            prism2 = App.ActiveDocument.addObject('PartDesign::AdditivePrism','Prism')
            body.addObject(prism2)
            prism2.Polygon = 6
            prism2.Circumradius = nutWidth / 2 / cos(math.radians(180/float(6)))
            prism2.Height = nutH
            prism2.Label = "Nut-right"
            prism2.AttachmentOffset = App.Placement(App.Vector(-slotWidth/2, 0.0, -nutDisplacement),  App.Rotation(0.0, 0.0, 0.0))
            prism2.MapReversed = False
            prism2.Support = [(App.activeDocument().XY_Plane,'')]
            prism2.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            #print ("\n" + self.d1.currentText() + " Bolt, nut and washer with slot created")

    # ===== Bolt, nut and large washer ==============================================
        elif self.d2.currentText() == "Bolt, nut and large washer":
            body = App.ActiveDocument.addObject("PartDesign::Body",self.d1.currentText() + ' Bolt nut and large washer')
            Gui.activeView().setActiveObject('pdbody', body)

            cylinder1 = App.ActiveDocument.addObject("PartDesign::AdditiveCylinder","Cylinder1")
            body.addObject(cylinder1)
            cylinder1.Radius = washerLargeR
            cylinder1.Height = headH + washerLargeH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cylinder2 = App.ActiveDocument.addObject("PartDesign::AdditiveCylinder","Cylinder2")
            body.addObject(cylinder2)
            cylinder2.Radius = bodyR
            cylinder2.Height = bodyH + headH + washerLargeH
            cylinder2.Label = "Body"
            cylinder2.AttachmentOffset = App.Placement(App.Vector(0.0, 0.0, 0.0),  App.Rotation(0.0, 0.0, 180.0))
            cylinder2.MapReversed = False
            cylinder2.Support = [(App.activeDocument().XY_Plane,'')]
            cylinder2.MapMode = 'FlatFace'

            prism = App.ActiveDocument.addObject("PartDesign::AdditivePrism","Prism")
            body.addObject(prism)
            prism.Polygon = 6
            prism.Circumradius = headR
            prism.Height = nutH
            prism.Label = "Nut"
            prism.AttachmentOffset = App.Placement(App.Vector(0.0, 0.0, -nutDisplacement),  App.Rotation(0.0, 0.0, 0.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Bolt, nut and large washer created")

    # ===== Bolt, nut and large washer (slot) ==============================================
        if self.d2.currentText() == "Bolt, nut and large washer" and slot == True:
            body = App.ActiveDocument.addObject("PartDesign::Body",self.d1.currentText() + ' Bolt nut and large washer with slot')
            Gui.activeView().setActiveObject('pdbody', body)
            App.ActiveDocument.recompute()

            cylinder1 = App.ActiveDocument.addObject("PartDesign::AdditiveCylinder","Cylinder1")
            body.addObject(cylinder1)
            cylinder1.Radius = washerLargeR
            cylinder1.Height = headH + washerLargeH
            cylinder1.Label = "Head-left"
            cylinder1.AttachmentOffset = App.Placement(App.Vector(slotWidth/2, 0.0, 0.0),  App.Rotation(0.0, 0.0, 0.0))
            cylinder1.MapReversed = True
            cylinder1.Support = [(App.activeDocument().XY_Plane,'')]
            cylinder1.MapMode = 'FlatFace'

            cube1 = App.ActiveDocument.addObject("PartDesign::AdditiveBox","Cube")
            body.addObject(cube1)
            cube1.Length = slotWidth
            cube1.Width = washerLargeR*2
            cube1.Height = headH + washerLargeH
            cube1.Label = "Head-center"
            cube1.AttachmentOffset = App.Placement(App.Vector(-slotWidth/2, -washerLargeR, -headH -washerLargeH),  App.Rotation(0.0, 0.0, 0.0))
            cube1.MapReversed = False
            cube1.Support = [(App.activeDocument().XY_Plane,'')]
            cube1.MapMode = 'FlatFace'

            cylinder2 = App.ActiveDocument.addObject("PartDesign::AdditiveCylinder","Cylinder1")
            body.addObject(cylinder2)
            cylinder2.Radius = washerLargeR
            cylinder2.Height = headH + washerLargeH
            cylinder2.Label = "Head-right"
            cylinder2.AttachmentOffset = App.Placement(App.Vector(-slotWidth/2, 0.0, 0.0),  App.Rotation(0.0, 0.0, 0.0))
            cylinder2.MapReversed = True
            cylinder2.Support = [(App.activeDocument().XY_Plane,'')]
            cylinder2.MapMode = 'FlatFace'

            cylinder3 = App.ActiveDocument.addObject("PartDesign::AdditiveCylinder","Cylinder1")
            body.addObject(cylinder3)
            cylinder3.Radius = bodyR
            cylinder3.Height = bodyH + headH + washerLargeH
            cylinder3.Label = "Body-left"
            cylinder3.AttachmentOffset = App.Placement(App.Vector(slotWidth/2, 0.0, 0.0),  App.Rotation(0.0, 0.0, 0.0))
            cylinder3.MapReversed = True
            cylinder3.Support = [(App.activeDocument().XY_Plane,'')]
            cylinder3.MapMode = 'FlatFace'

            cube2 = App.ActiveDocument.addObject("PartDesign::AdditiveBox","Cube")
            body.addObject(cube2)
            cube2.Length = slotWidth
            cube2.Width = bodyR*2
            cube2.Height = bodyH + headH + washerLargeH
            cube2.Label = "Body-center"
            cube2.AttachmentOffset = App.Placement(App.Vector(-slotWidth/2, -bodyR, -bodyH - headH - washerLargeH),  App.Rotation(0.0, 0.0, 0.0))
            cube2.MapReversed = False
            cube2.Support = [(App.activeDocument().XY_Plane,'')]
            cube2.MapMode = 'FlatFace'

            cylinder4 = App.ActiveDocument.addObject("PartDesign::AdditiveCylinder","Cylinder1")
            body.addObject(cylinder4)
            cylinder4.Radius = bodyR
            cylinder4.Height = bodyH + headH + washerLargeH
            cylinder4.Label = "Body-right"
            cylinder4.AttachmentOffset = App.Placement(App.Vector(-slotWidth/2, 0.0, 0.0),  App.Rotation(0.0, 0.0, 0.0))
            cylinder4.MapReversed = True
            cylinder4.Support = [(App.activeDocument().XY_Plane,'')]
            cylinder4.MapMode = 'FlatFace'

            prism1 = App.ActiveDocument.addObject('PartDesign::AdditivePrism','Prism')
            body.addObject(prism1)
            prism1.Polygon = 6
            prism1.Circumradius = nutWidth / 2 / cos(math.radians(180/float(6)))
            prism1.Height = nutH
            prism1.Label = "Nut-left"
            prism1.AttachmentOffset = App.Placement(App.Vector(slotWidth/2, 0.0, -nutDisplacement),  App.Rotation(0.0, 0.0, 0.0))
            prism1.MapReversed = False
            prism1.Support = [(App.activeDocument().XY_Plane,'')]
            prism1.MapMode = 'FlatFace'

            cube3 = App.ActiveDocument.addObject("PartDesign::AdditiveBox","Cube")
            body.addObject(cube3)
            cube3.Length = slotWidth
            cube3.Width = nutWidth
            cube3.Height = nutH
            cube3.Label = "Nut-center"
            cube3.AttachmentOffset = App.Placement(App.Vector(-slotWidth/2, -nutWidth/2, -nutDisplacement),  App.Rotation(0.0, 0.0, 0.0))
            cube3.MapReversed = False
            cube3.Support = [(App.activeDocument().XY_Plane,'')]
            cube3.MapMode = 'FlatFace'

            prism2 = App.ActiveDocument.addObject('PartDesign::AdditivePrism','Prism')
            body.addObject(prism2)
            prism2.Polygon = 6
            prism2.Circumradius = nutWidth / 2 / cos(math.radians(180/float(6)))
            prism2.Height = nutH
            prism2.Label = "Nut-right"
            prism2.AttachmentOffset = App.Placement(App.Vector(-slotWidth/2, 0.0, -nutDisplacement),  App.Rotation(0.0, 0.0, 0.0))
            prism2.MapReversed = False
            prism2.Support = [(App.activeDocument().XY_Plane,'')]
            prism2.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            #print ("\n" + self.d1.currentText() + " Bolt, nut and large washer with slot created")

    # ===== Bolt, grooved nut and washer ==============================================
        elif self.d2.currentText() == "Bolt, grooved nut and washer":
            body = App.ActiveDocument.addObject("PartDesign::Body",self.d1.currentText() + ' Bolt grooved nut and washer')
            Gui.activeView().setActiveObject('pdbody', body)

            cylinder1 = App.ActiveDocument.addObject("PartDesign::AdditiveCylinder","Cylinder1")
            body.addObject(cylinder1)
            cylinder1.Radius = washerR
            cylinder1.Height = headH + washerH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cylinder2 = App.ActiveDocument.addObject("PartDesign::AdditiveCylinder","Cylinder2")
            body.addObject(cylinder2)
            cylinder2.Radius = bodyR
            cylinder2.Height = bodyH + headH + washerH
            cylinder2.Label = "Body"
            cylinder2.AttachmentOffset = App.Placement(App.Vector(0.0, 0.0, 0.0),  App.Rotation(0.0, 0.0, 180.0))
            cylinder2.MapReversed = False
            cylinder2.Support = [(App.activeDocument().XY_Plane,'')]
            cylinder2.MapMode = 'FlatFace'

            cube = App.ActiveDocument.addObject("PartDesign::AdditiveBox","Cube")
            body.addObject(cube)
            cube.Length = grooveLength
            cube.Width = nutWidth
            cube.Height = nutH
            cube.Label = "Groove"
            cube.AttachmentOffset = App.Placement(App.Vector(0.0, -cube.Width/2,-nutDisplacement),  App.Rotation(0.0, 0.0, 0.0))
            cube.MapReversed = False
            cube.Support = [(App.activeDocument().XY_Plane,'')]
            cube.MapMode = 'FlatFace'

            prism = App.ActiveDocument.addObject("PartDesign::AdditivePrism","Prism")
            body.addObject(prism)
            prism.Polygon = 6
            prism.Circumradius = nutWidth / 2 / cos(math.radians(180/float(6)))
            prism.Height = nutH
            prism.Label = "Nut"
            prism.AttachmentOffset = App.Placement(App.Vector(0.0, 0.0, -nutDisplacement),  App.Rotation(0.0, 0.0, 0.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Bolt, grooved nut and washer created")

    # ===== Bolt, grooved nut and large washer ==============================================
        elif self.d2.currentText() == "Bolt, grooved nut and large washer":
            body = App.ActiveDocument.addObject("PartDesign::Body",self.d1.currentText() + ' Bolt grooved nut and large washer')
            Gui.activeView().setActiveObject('pdbody', body)

            cylinder1 = App.ActiveDocument.addObject("PartDesign::AdditiveCylinder","Cylinder1")
            body.addObject(cylinder1)
            cylinder1.Radius = washerLargeR
            cylinder1.Height = headH + washerLargeH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cylinder2 = App.ActiveDocument.addObject("PartDesign::AdditiveCylinder","Cylinder2")
            body.addObject(cylinder2)
            cylinder2.Radius = bodyR
            cylinder2.Height = bodyH + headH + washerLargeH
            cylinder2.Label = "Body"
            cylinder2.AttachmentOffset = App.Placement(App.Vector(0.0, 0.0, 0.0),  App.Rotation(0.0, 0.0, 180.0))
            cylinder2.MapReversed = False
            cylinder2.Support = [(App.activeDocument().XY_Plane,'')]
            cylinder2.MapMode = 'FlatFace'

            cube = App.ActiveDocument.addObject("PartDesign::AdditiveBox","Cube")
            body.addObject(cube)
            cube.Length = grooveLength
            cube.Width = nutWidth
            cube.Height = nutH
            cube.Label = "Groove"
            cube.AttachmentOffset = App.Placement(App.Vector(0.0, -cube.Width/2,-nutDisplacement),  App.Rotation(0.0, 0.0, 0.0))
            cube.MapReversed = False
            cube.Support = [(App.activeDocument().XY_Plane,'')]
            cube.MapMode = 'FlatFace'

            prism = App.ActiveDocument.addObject("PartDesign::AdditivePrism","Prism")
            body.addObject(prism)
            prism.Polygon = 6
            prism.Circumradius = nutWidth / 2 / cos(math.radians(180/float(6)))
            prism.Height = nutH
            prism.Label = "Nut"
            prism.AttachmentOffset = App.Placement(App.Vector(0.0, 0.0, -nutDisplacement),  App.Rotation(0.0, 0.0, 0.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Bolt, grooved nut and washer created")

    # ===== Nut ==============================================
        elif self.d2.currentText() == "Nut" and slot == False:
            body = App.ActiveDocument.addObject("PartDesign::Body",self.d1.currentText() + ' Nut')
            Gui.activeView().setActiveObject('pdbody', body)

            prism = App.ActiveDocument.addObject("PartDesign::AdditivePrism","Prism")
            body.addObject(prism)
            prism.Polygon = 6
            prism.Circumradius = nutWidth / 2 / cos(math.radians(180/float(6)))
            prism.Height = nutH
            prism.Label = "Nut"
            prism.AttachmentOffset = App.Placement(App.Vector(0.0, 0.0, 0.0),  App.Rotation(0.0, 0.0, 180.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency
            Gui.activeView().setActiveObject('pdbody', None)
            App.ActiveDocument.getObject(groupName).addObject(body)
            App.ActiveDocument.recompute()

            print ("\n" + self.d1.currentText() + " Nut created")

    # ===== Nut (slot) ==============================================
        elif self.d2.currentText() == "Nut" and slot == True:
            body = App.ActiveDocument.addObject("PartDesign::Body",self.d1.currentText() + ' Nut with slot')
            Gui.activeView().setActiveObject('pdbody', body)

            prism = App.ActiveDocument.addObject("PartDesign::AdditivePrism","Prism")
            body.addObject(prism)
            prism.Polygon = 6
            prism.Circumradius = nutWidth / 2 / cos(math.radians(180/float(6)))
            prism.Height = nutH
            prism.Label = "Nut with slot"
            prism.AttachmentOffset = App.Placement(App.Vector(0.0, 0.0, 0.0),  App.Rotation(0.0, 0.0, 180.0))
            prism.MapReversed = False
            prism.Support = [(App.activeDocument().XY_Plane,'')]
            prism.MapMode = 'FlatFace'



            prism1 = App.ActiveDocument.addObject('PartDesign::AdditivePrism','Prism')
            body.addObject(prism1)
            prism1.Polygon = 6
            prism1.Circumradius = nutWidth / 2 / cos(math.radians(180/float(6)))
            prism1.Height = nutH
            prism1.Label = "Nut-left"
            prism1.AttachmentOffset = App.Placement(App.Vector(slotWidth/2, 0.0, 0.0),  App.Rotation(0.0, 0.0, 180.0))
            prism1.MapReversed = False
            prism1.Support = [(App.activeDocument().XY_Plane,'')]
            prism1.MapMode = 'FlatFace'

            cube = App.ActiveDocument.addObject("PartDesign::AdditiveBox","Cube")
            body.addObject(cube)
            cube.Length = slotWidth
            cube.Width = nutWidth
            cube.Height = nutH
            cube.Label = "Nut-center"
            cube.AttachmentOffset = App.Placement(App.Vector(-slotWidth/2, -nutWidth/2, -nutH),  App.Rotation(0.0, 0.0, 0.0))
            cube.MapReversed = False
            cube.Support = [(App.activeDocument().XY_Plane,'')]
            cube.MapMode = 'FlatFace'

            prism2 = App.ActiveDocument.addObject('PartDesign::AdditivePrism','Prism')
            body.addObject(prism2)
            prism2.Polygon = 6
            prism2.Circumradius = nutWidth / 2 / cos(math.radians(180/float(6)))
            prism2.Height = nutH
            prism2.Label = "Nut-right"
            prism2.AttachmentOffset = App.Placement(App.Vector(-slotWidth/2, 0.0, 0.0),  App.Rotation(0.0, 0.0, 180.0))
            prism2.MapReversed = False
            prism2.Support = [(App.activeDocument().XY_Plane,'')]
            prism2.MapMode = 'FlatFace'

            body.Placement.Base = App.Vector(originX, originY, originZ)
            body.Placement.Rotation = rot.Q

            Gui.activeDocument().activeObject().ShapeColor = bodyColor
            Gui.activeDocument().activeObject().Transparency = bodyTransparency
            Gui.activeView().setActiveObject('pdbody', None)
            App.ActiveDocument.getObject(groupName).addObject(body)
            App.ActiveDocument.recompute()

            print ("\n" + self.d1.currentText() + " Nut with slot created")

    # ===== Grooved nut ==============================================
        elif self.d2.currentText() == "Grooved nut":
            body = App.ActiveDocument.addObject("PartDesign::Body",self.d1.currentText() + ' Grooved nut')
            Gui.activeView().setActiveObject('pdbody', body)

            cube = App.ActiveDocument.addObject("PartDesign::AdditiveBox","Cube")
            body.addObject(cube)
            cube.Length = grooveLength
            cube.Width = nutWidth
            cube.Height = nutH
            cube.Label = "Groove"
            cube.AttachmentOffset = App.Placement(App.Vector(0.0, -cube.Width/2, -nutH),  App.Rotation(0.0, 0.0, 0.0))
            cube.MapReversed = False
            cube.Support = [(App.activeDocument().XY_Plane,'')]
            cube.MapMode = 'FlatFace'

            prism = App.ActiveDocument.addObject("PartDesign::AdditivePrism","Prism")
            body.addObject(prism)
            prism.Polygon = 6
            prism.Circumradius = nutWidth / 2 / cos(math.radians(180/float(6)))
            prism.Height = nutH
            prism.Label = "Nut"
            prism.AttachmentOffset = App.Placement(App.Vector(0.0, 0.0, 0.0),  App.Rotation(0.0, 0.0, 180.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Grooved nut created")

    # ===== Nut and washer ==============================================
        elif self.d2.currentText() == "Nut and washer" and slot == False:
            body = App.ActiveDocument.addObject("PartDesign::Body",self.d1.currentText() + ' Nut and washer')
            Gui.activeView().setActiveObject('pdbody', body)

            cylinder1 = App.ActiveDocument.addObject("PartDesign::AdditiveCylinder","Cylinder1")
            body.addObject(cylinder1)
            cylinder1.Radius = washerR
            cylinder1.Height = nutH + washerH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            body.Placement.Base = App.Vector(originX, originY, originZ)
            body.Placement.Rotation = rot.Q

            Gui.activeDocument().activeObject().ShapeColor = bodyColor
            Gui.activeDocument().activeObject().Transparency = bodyTransparency
            Gui.activeView().setActiveObject('pdbody', None)
            App.ActiveDocument.getObject(groupName).addObject(body)
            App.ActiveDocument.recompute()

            print ("\n" + self.d1.currentText() + " Nut and washer created")

    # ===== Nut and washer (slot) ==============================================
        elif self.d2.currentText() == "Nut and washer" and slot == True:
            body = App.ActiveDocument.addObject("PartDesign::Body",self.d1.currentText() + ' Nut and washer with slot')
            Gui.activeView().setActiveObject('pdbody', body)

            cylinder1 = App.ActiveDocument.addObject("PartDesign::AdditiveCylinder","Cylinder1")
            body.addObject(cylinder1)
            cylinder1.Radius = washerR
            cylinder1.Height = nutH + washerH
            cylinder1.Label = "Head-left"
            cylinder1.AttachmentOffset = App.Placement(App.Vector(slotWidth/2, 0.0, 0.0),  App.Rotation(0.0, 0.0, 0.0))
            cylinder1.MapReversed = True
            cylinder1.Support = [(App.activeDocument().XY_Plane,'')]
            cylinder1.MapMode = 'FlatFace'

            cube1 = App.ActiveDocument.addObject("PartDesign::AdditiveBox","Cube")
            body.addObject(cube1)
            cube1.Length = slotWidth
            cube1.Width = washerR*2
            cube1.Height = nutH + washerH
            cube1.Label = "Head-center"
            cube1.AttachmentOffset = App.Placement(App.Vector(-slotWidth/2, -washerR, -nutH - washerH),  App.Rotation(0.0, 0.0, 0.0))
            cube1.MapReversed = False
            cube1.Support = [(App.activeDocument().XY_Plane,'')]
            cube1.MapMode = 'FlatFace'

            cylinder2 = App.ActiveDocument.addObject("PartDesign::AdditiveCylinder","Cylinder1")
            body.addObject(cylinder2)
            cylinder2.Radius = washerR
            cylinder2.Height = nutH + washerH
            cylinder2.Label = "Head-right"
            cylinder2.AttachmentOffset = App.Placement(App.Vector(-slotWidth/2, 0.0, 0.0),  App.Rotation(0.0, 0.0, 0.0))
            cylinder2.MapReversed = True
            cylinder2.Support = [(App.activeDocument().XY_Plane,'')]
            cylinder2.MapMode = 'FlatFace'

            body.Placement.Base = App.Vector(originX, originY, originZ)
            body.Placement.Rotation = rot.Q

            Gui.activeDocument().activeObject().ShapeColor = bodyColor
            Gui.activeDocument().activeObject().Transparency = bodyTransparency
            Gui.activeView().setActiveObject('pdbody', None)
            App.ActiveDocument.getObject(groupName).addObject(body)
            App.ActiveDocument.recompute()

            print ("\n" + self.d1.currentText() + " Nut and washer with slot created")

    # ===== Nut and large washer ==============================================
        elif self.d2.currentText() == "Nut and large washer" and slot == False:
            body = App.ActiveDocument.addObject("PartDesign::Body",self.d1.currentText() + ' Nut and large washer')
            Gui.activeView().setActiveObject('pdbody', body)

            cylinder1 = App.ActiveDocument.addObject("PartDesign::AdditiveCylinder","Cylinder1")
            body.addObject(cylinder1)
            cylinder1.Radius = washerLargeR
            cylinder1.Height = nutH + washerLargeH
            cylinder1.Label = "Head"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            body.Placement.Base = App.Vector(originX, originY, originZ)
            body.Placement.Rotation = rot.Q

            Gui.activeDocument().activeObject().ShapeColor = bodyColor
            Gui.activeDocument().activeObject().Transparency = bodyTransparency
            Gui.activeView().setActiveObject('pdbody', None)
            App.ActiveDocument.getObject(groupName).addObject(body)
            App.ActiveDocument.recompute()

            print ("\n" + self.d1.currentText() + " Nut and large washer created")

    # ===== Nut and large washer (slot) ==============================================
        elif self.d2.currentText() == "Nut and large washer" and slot == True:
            body = App.ActiveDocument.addObject("PartDesign::Body",self.d1.currentText() + ' Nut and large washer with slot')
            Gui.activeView().setActiveObject('pdbody', body)

            cylinder1 = App.ActiveDocument.addObject("PartDesign::AdditiveCylinder","Cylinder1")
            body.addObject(cylinder1)
            cylinder1.Radius = washerLargeR
            cylinder1.Height = nutH + washerLargeH
            cylinder1.Label = "Head-left"
            cylinder1.AttachmentOffset = App.Placement(App.Vector(slotWidth/2, 0.0, 0.0),  App.Rotation(0.0, 0.0, 0.0))
            cylinder1.MapReversed = True
            cylinder1.Support = [(App.activeDocument().XY_Plane,'')]
            cylinder1.MapMode = 'FlatFace'

            cube1 = App.ActiveDocument.addObject("PartDesign::AdditiveBox","Cube")
            body.addObject(cube1)
            cube1.Length = slotWidth
            cube1.Width = washerLargeR*2
            cube1.Height = nutH + washerLargeH
            cube1.Label = "Head-center"
            cube1.AttachmentOffset = App.Placement(App.Vector(-slotWidth/2, -washerLargeR, -nutH - washerLargeH),  App.Rotation(0.0, 0.0, 0.0))
            cube1.MapReversed = False
            cube1.Support = [(App.activeDocument().XY_Plane,'')]
            cube1.MapMode = 'FlatFace'

            cylinder2 = App.ActiveDocument.addObject("PartDesign::AdditiveCylinder","Cylinder1")
            body.addObject(cylinder2)
            cylinder2.Radius = washerLargeR
            cylinder2.Height = nutH + washerLargeH
            cylinder2.Label = "Head-right"
            cylinder2.AttachmentOffset = App.Placement(App.Vector(-slotWidth/2, 0.0, 0.0),  App.Rotation(0.0, 0.0, 0.0))
            cylinder2.MapReversed = True
            cylinder2.Support = [(App.activeDocument().XY_Plane,'')]
            cylinder2.MapMode = 'FlatFace'

            body.Placement.Base = App.Vector(originX, originY, originZ)
            body.Placement.Rotation = rot.Q

            Gui.activeDocument().activeObject().ShapeColor = bodyColor
            Gui.activeDocument().activeObject().Transparency = bodyTransparency
            Gui.activeView().setActiveObject('pdbody', None)
            App.ActiveDocument.getObject(groupName).addObject(body)
            App.ActiveDocument.recompute()

            print ("\n" + self.d1.currentText() + " Nut and large washer with slot created")

    # ===== Grooved nut and washer ==============================================
        elif self.d2.currentText() == "Grooved nut and washer":
            body = App.ActiveDocument.addObject("PartDesign::Body",self.d1.currentText() + ' Grooved nut and large washer')
            Gui.activeView().setActiveObject('pdbody', body)

            cylinder1 = App.ActiveDocument.addObject("PartDesign::AdditiveCylinder","Cylinder1")
            body.addObject(cylinder1)
            cylinder1.Radius = washerR
            cylinder1.Height = washerH
            cylinder1.Label = "Washer"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cube1 = App.ActiveDocument.addObject("PartDesign::AdditiveBox","Cube1")
            body.addObject(cube1)
            cube1.Length = grooveLength
            cube1.Width = washerR * 2
            cube1.Height = washerH
            cube1.Label = "Washer groove"
            cube1.AttachmentOffset = App.Placement(App.Vector(0.0, -cube1.Width/2, -washerH),  App.Rotation(0.0, 0.0, 0.0))
            cube1.MapReversed = False
            cube1.Support = [(App.activeDocument().XY_Plane,'')]
            cube1.MapMode = 'FlatFace'

            cube2 = App.ActiveDocument.addObject("PartDesign::AdditiveBox","Cube2")
            body.addObject(cube2)
            cube2.Length = grooveLength
            cube2.Width = nutWidth
            cube2.Height = nutH
            cube2.Label = "Nut groove"
            cube2.AttachmentOffset = App.Placement(App.Vector(0.0, -cube2.Width/2, -washerH-nutH),  App.Rotation(0.0, 0.0, 0.0))
            cube2.MapReversed = False
            cube2.Support = [(App.activeDocument().XY_Plane,'')]
            cube2.MapMode = 'FlatFace'

            prism = App.ActiveDocument.addObject("PartDesign::AdditivePrism","Prism")
            body.addObject(prism)
            prism.Polygon = 6
            prism.Circumradius = nutWidth / 2 / cos(math.radians(180/float(6)))
            prism.Height = nutH
            prism.Label = "Nut"
            prism.AttachmentOffset = App.Placement(App.Vector(0.0, 0.0, -washerH),  App.Rotation(0.0, 0.0, 180.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Grooved nut and washer created")

    # ===== Grooved nut and large washer ==============================================
        elif self.d2.currentText() == "Grooved nut and large washer":
            body = App.ActiveDocument.addObject("PartDesign::Body",self.d1.currentText() + ' Grooved nut and large large washer')
            Gui.activeView().setActiveObject('pdbody', body)

            cylinder1 = App.ActiveDocument.addObject("PartDesign::AdditiveCylinder","Cylinder1")
            body.addObject(cylinder1)
            cylinder1.Radius = washerLargeR
            cylinder1.Height = washerLargeH
            cylinder1.Label = "Washer"
            cylinder1.AttachmentOffset = App.Placement(App.Vector(0.0, 0.0, 0.0),  App.Rotation(0.0, 0.0, 180.0))
            cylinder1.MapReversed = False
            cylinder1.Support = [(App.activeDocument().XY_Plane,'')]
            cylinder1.MapMode = 'FlatFace'

            cube1 = App.ActiveDocument.addObject("PartDesign::AdditiveBox","Cube1")
            body.addObject(cube1)
            cube1.Length = grooveLength
            cube1.Width = washerLargeR * 2
            cube1.Height = washerLargeH
            cube1.Label = "Washer groove"
            cube1.AttachmentOffset = App.Placement(App.Vector(0.0, -cube1.Width/2, -washerLargeH),  App.Rotation(0.0, 0.0, 0.0))
            cube1.MapReversed = False
            cube1.Support = [(App.activeDocument().XY_Plane,'')]
            cube1.MapMode = 'FlatFace'

            cube2 = App.ActiveDocument.addObject("PartDesign::AdditiveBox","Cube2")
            body.addObject(cube2)
            cube2.Length = grooveLength
            cube2.Width = nutWidth
            cube2.Height = nutH
            cube2.Label = "Nut groove"
            cube2.AttachmentOffset = App.Placement(App.Vector(0.0, -cube2.Width/2, -washerLargeH-nutH),  App.Rotation(0.0, 0.0, 0.0))
            cube2.MapReversed = False
            cube2.Support = [(App.activeDocument().XY_Plane,'')]
            cube2.MapMode = 'FlatFace'

            prism = App.ActiveDocument.addObject("PartDesign::AdditivePrism","Prism")
            body.addObject(prism)
            prism.Polygon = 6
            prism.Circumradius = nutWidth / 2 / cos(math.radians(180/float(6)))
            prism.Height = nutH
            prism.Label = "Nut"
            prism.AttachmentOffset = App.Placement(App.Vector(0.0, 0.0, -washerLargeH),  App.Rotation(0.0, 0.0, 180.0))
            prism.MapReversed = False
            prism.Support = [(App.activeDocument().XY_Plane,'')]
            prism.MapMode = 'FlatFace'

            body.Placement.Base = App.Vector(originX, originY, originZ)
            body.Placement.Rotation = rot.Q

            Gui.activeDocument().activeObject().ShapeColor = bodyColor
            Gui.activeDocument().activeObject().Transparency = bodyTransparency

            Gui.activeDocument().activeObject().Visibility = False
            Gui.activeDocument().activeObject().Visibility = True
            Gui.activeView().setActiveObject('pdbody', None)
            App.ActiveDocument.getObject(groupName).addObject(body)
            App.ActiveDocument.recompute()

            print ("\n" + self.d1.currentText() + " Grooved nut and large washer created")

    # ===== If errors ==============================================
        else:
            FreeCAD.Console.PrintError("\nError or 'TODO'")

        App.ActiveDocument.recompute()
        # Gui.SendMsgToActiveView("ViewFit")
        print ("\n********* END *********")

###############################################################################################################


def Alg_singleInstance():
    app = QtGui.QApplication

    for i in app.topLevelWidgets():
        if i.objectName() == "fastenerHoles":
            i.deleteLater()
        else:
            pass
    t=FreeCADGui.getMainWindow()
    dw=t.findChildren(QtGui.QDockWidget)
    #print str(dw)
    for i in dw:
        #say str(i.objectName())
        if str(i.objectName()) == "fastenerHoles":
            i.deleteLater()
        else:
            pass
##

def Alg_checkInstance():
    app = QtGui.QApplication

    foundAlg=False
    for i in app.topLevelWidgets():
        if i.objectName() == "fastenerHoles":
            foundAlg=True
        else:
            pass
    t=FreeCADGui.getMainWindow()
    dw=t.findChildren(QtGui.QDockWidget)
    #print str(dw)
    for i in dw:
        #say str(i.objectName())
        if str(i.objectName()) == "fastenerHoles":
            foundAlg=True
        else:
            pass
    return foundAlg
##

##############################################################

doc=FreeCAD.ActiveDocument

Alg_singleInstance()

ALGDockWidget = QtGui.QDockWidget()     # create a new dockwidget
ALGDockWidget.ui = Ui_DockWidget()      # load the Ui script
ALGDockWidget.ui.setupUi(ALGDockWidget) # setup the Ui
#ui = Ui_AlignDockWidget()
#ui.setupUi(AlignDockWidget)
#AlignDockWidget.show()

ALGDockWidget.setObjectName("fastenerHoles")

ALGDockWidget.setFloating(True)         #undock
ALGDockWidget.resize(sizeX,sizeY)
ALGDockWidget.activateWindow()
ALGDockWidget.raise_()

#ALGDockWidget.show()

ALGDockWidget.setFeatures( QtGui.QDockWidget.DockWidgetMovable | QtGui.QDockWidget.DockWidgetFloatable|QtGui.QDockWidget.DockWidgetClosable )
#
# if ALGDockWidget.style().metaObject().className()== "QStyleSheetStyle":
#     ALGDockWidget.setStyleSheet('QPushButton {border-radius: 0px; padding: 1px 2px;}')

ALGmw = FreeCADGui.getMainWindow()      # PySide # the active qt window = the freecad window since we are inside it
ALGmw.addDockWidget(QtCore.Qt.RightDockWidgetArea,ALGDockWidget)
#ALGDockWidget.show()
Alg_undock()

### ------------------------------------------------------------------------------------ ###
